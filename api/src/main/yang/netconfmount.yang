module netconfmount {
    yang-version 1;
    namespace "urn:opendaylight:params:xml:ns:yang:netconfmount";
    prefix "netconfmount";

    revision "2015-01-05" {
        description "Initial revision of netconfmount model";
    }
}
